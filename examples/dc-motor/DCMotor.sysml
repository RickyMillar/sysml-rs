package DCMotorModel {
    doc /* DC motor cross-domain transformer: electrical -> mechanical.
     *
     * Coupling equations (motor constant Kt = 0.1 Nm/A):
     *   back_emf   = Kt * omega          (back-EMF, V)
     *   torque     = Kt * current        (electromagnetic torque, Nm)
     *
     * Mechanical ODE (rotor dynamics):
     *   d(omega)/dt = (torque - friction * omega) / inertia
     *
     * Parameters:
     *   Kt       = 0.1  Nm/A  (motor constant)
     *   inertia  = 0.01 kg*m^2 (rotor moment of inertia)
     *   friction = 0.001 Nm*s/rad (viscous friction coefficient)
     *
     * The ODE is solved by the SSR GetDerivative pattern each tick.
     * Electrical inputs (voltage, current) are updated externally by
     * the electrical subsystem.
     *
     * Uses spec-standard StateSpaceRepresentation pattern:
     * calc def :> GetDerivative defines dx/dt = f(u, x).
     * Bond-graph transformer: e_out = r * e_in, f_in + r * f_out = 0 */

    private import ISQ::*;
    private import SI::*;
    private import ScalarValues::*;
    private import StateSpaceRepresentation::*;

    // -- Port definitions --------------------------------------------------

    item def ElectricalSignal {
        doc /* Electrical port payload: voltage and current. */
        attribute voltage : ElectricPotentialValue;
        attribute current : ElectricCurrentValue;
    }

    item def MechanicalSignal {
        doc /* Mechanical shaft payload: angular velocity and torque. */
        attribute angular_velocity : AngularVelocityValue;
        attribute torque : TorqueValue;
    }

    port def PhaseInPort {
        doc /* Electrical input port (AC or DC supply). */
        in item power : ElectricalSignal;
    }

    port def ShaftPort {
        doc /* Mechanical output port (rotating shaft). */
        out item shaft : MechanicalSignal;
    }

    // -- DC Motor part definition ------------------------------------------

    part def DCMotor {
        doc /* Permanent-magnet DC motor modelled as a cross-domain transformer.
         *
         * Electrical domain input:
         *   voltage (V) and current (A) arrive on phaseIn port.
         *
         * Mechanical domain output:
         *   omega (rad/s) and torque (Nm) leave on shaftOut port.
         *
         * Transformer constitutive relations:
         *   back_emf = Kt * omega
         *   torque   = Kt * current
         *
         * The ODE integrates omega forward in time given net torque
         * and viscous friction. */

        // Physical ports
        port phaseIn  : PhaseInPort;
        port shaftOut : ShaftPort;

        // -- Motor parameters ----------------------------------------------

        // Motor constant (Nm/A = V*s/rad)
        attribute Kt : Real default 0.1;

        // Rotor moment of inertia (kg*m^2)
        attribute inertia : Real default 0.01;

        // Viscous friction coefficient (Nm*s/rad)
        attribute friction : Real default 0.001;

        // -- Electrical inputs (driven by external circuit) ----------------

        attribute voltage : ElectricPotentialValue default 0.0;
        attribute current : ElectricCurrentValue default 0.0;

        // -- Transformer coupling (computed attributes) --------------------

        // Back-EMF: voltage generated by spinning rotor (V)
        attribute back_emf : ElectricPotentialValue default 0.0;

        // Electromagnetic torque delivered to shaft (Nm)
        attribute torque : TorqueValue default 0.0;

        // -- ODE state variable --------------------------------------------

        // Angular velocity of the shaft (rad/s)
        out attribute omega : AngularVelocityValue default 0.0;

        // -- SSR derivative -- spec-standard GetDerivative pattern ---------

        // d(omega)/dt = (Kt * current - friction * omega) / inertia
        calc def OmegaDerivative :> GetDerivative {
            return domegadt = (Kt * current - friction * omega) / inertia;
        }

        // -- Constraints: transformer constitutive relations ---------------

        assert constraint backEmfCoupling {
            doc /* back_emf must equal Kt * omega (transformer effort equation). */
            back_emf == Kt * omega
        }

        assert constraint torqueCoupling {
            doc /* torque must equal Kt * current (transformer flow equation). */
            torque == Kt * current
        }
    }
}
