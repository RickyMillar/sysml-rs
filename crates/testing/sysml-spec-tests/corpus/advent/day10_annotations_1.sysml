package L10_Annotations {
    part def SantaSleigh {
        doc locale "en_US"
        /* This version of Santa's sleigh demonstrates how to specify
        * elements in other languages.
        */

        doc docHu locale "hu_HU"
        /* A Mikulas szanjanak ezen verzioja bemutatja, hogyan adhato
        * meg egy modellelem mas nyelveken is.
        */

        doc docLt locale "lt_LT"
        /* Si Kaledu Senelio rogiu versija parodo, kaip nurodyti modelio
        * elementus kitomis kalbomis.
        */

        ref item santa {
            //...
        }
    }
}
