package L10_Annotations {
    part def SantaSleigh {
        //...
        ref item santa {
            //...
            action greet {
                // We will learn about actions in a later episode

                language "python"
                /* print("Ho ho ho! Merry Christmas!") */

                rep inAlf language "alf"
                /* WriteLine("Ho ho ho! Merry Christmas!"); */
            }
        }
    }
}
