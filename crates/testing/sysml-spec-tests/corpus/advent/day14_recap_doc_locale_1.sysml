package AdventDay14_Example1 {

    part def SantaSleigh {
        doc locale "en_US"
        /* This version of Santa's sleigh demonstrates how to specify
         * elements in other languages.
         */

        doc docHu locale "hu_HU"
        /* A Mikulas szanjan ezen verzioja bemutatja... */
    }
}
